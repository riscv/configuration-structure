Configuration-Structure
DEFINITIONS
   AUTOMATIC TAGS ::=
BEGIN
   IMPORTS Debug, DebugModule FROM Debug-Extension
         Range, FlexibleRange, FlexibleRange4, FlexibleRange8, FlexibleRange16
               FROM Helper-Types
         Zjpm FROM Zjpm-Extension;

   Hart ::= SEQUENCE {
      hartid CHOICE { /* 4 choices use 2-bit as the index*/
        hartId4  FlexibleRange4, /* For hart number [1..4] */
        hartId8  FlexibleRange8, /* For hart number [1..8] */
        hartId16 FlexibleRange16, /* For hart number [1..16] */
        hartId   FlexibleRange   /* For hart number > 16 */
      },
      debug Debug OPTIONAL,
      isa Isa OPTIONAL,
      privileged Privileged OPTIONAL,
      clic Clic OPTIONAL,
      fastInt FastInt OPTIONAL,
      zjpm Zjpm OPTIONAL,
      ...
   }
   Tuple ::= SEQUENCE {
      value INTEGER,
      mask INTEGER
   }
   Triple ::= SEQUENCE {
      low INTEGER,
      high INTEGER,
      mask INTEGER
   }
   PossibleValues ::= SEQUENCE {
      tuple SEQUENCE OF Tuple OPTIONAL,
      triple SEQUENCE OF Triple OPTIONAL,
      ...
   }
   Configuration ::= SEQUENCE {
      harts SEQUENCE OF Hart OPTIONAL,
      debugModule SEQUENCE OF DebugModule OPTIONAL,
      traceModule TraceModule OPTIONAL,
      physicalMemory SEQUENCE OF PhysicalMemory OPTIONAL,
      ...
   }
   Isa ::= SEQUENCE {
      -- This is a placeholder, which should be filled out with help from the
      -- ISA group.
      riscv32 BOOLEAN OPTIONAL,
      riscv64 BOOLEAN OPTIONAL,
      riscv128 BOOLEAN OPTIONAL,
      ...
   }
   PrivModes ::= SEQUENCE {
      u BOOLEAN,
      m BOOLEAN,
      s BOOLEAN
   }
   PrivSatps ::= SEQUENCE {
      sv32 BOOLEAN,
      sv39 BOOLEAN,
      sv48 BOOLEAN,
      sv57 BOOLEAN,
      sv64 BOOLEAN
   }
   Privileged ::= SEQUENCE {
      -- This is a placeholder, which should be filled out with help from the
      -- Privileged group.
      modes PrivModes OPTIONAL,
      satps PrivSatps OPTIONAL,
      epmp BOOLEAN OPTIONAL,
      ...
   }
   Clic ::= SEQUENCE {
      -- This is a placeholder, which should be filled out with help from the
      -- fast interrupts group. It should probably be moved into the FastInt
      -- section.
      mTimeRegisterAddress INTEGER OPTIONAL,
      mTimeCompareRegisterAddress INTEGER OPTIONAL,
      ...
   }
   TraceModule ::= SEQUENCE {
      -- This is a placeholder, which should be filled out with help from the
      -- trace group.
      branchPredictorEntries INTEGER OPTIONAL,
      jumpTargetCacheEntries INTEGER OPTIONAL,
      contextBusWidth INTEGER OPTIONAL,
      ...
   }
   PhysicalMemory ::= SEQUENCE {
      -- This is a placeholder that might be useful, but there's no obvious task
      -- group who would fill it out.
      address SEQUENCE OF Range,
      cacheable BOOLEAN OPTIONAL,
      lrScSupported BOOLEAN OPTIONAL,
      ...
   }
   FastInt ::= SEQUENCE {
      -- This is a placeholder, which should be filled out with help from the
      -- fast interrupts group.
      mModeTimeRegAddr INTEGER OPTIONAL,
      mModeTimeCompRegAddr INTEGER OPTIONAL,
      ...
   }
END

Helper-Types
DEFINITIONS
   AUTOMATIC TAGS ::=
BEGIN
   EXPORTS FlexibleRange, FlexibleRange4, FlexibleRange8, FlexibleRange16,
         Range;

   -- 2-bit integer
   Integer4 ::= INTEGER (0..3)

   -- 3-bit integer
   Integer8 ::= INTEGER (0..7)

   -- 4-bit integer
   Integer16 ::= INTEGER (0..15)

   -- 2-bit integer of range [0..3]
   Range4 ::= SEQUENCE {
      start Integer4,
      length Integer4
   }
   -- 3-bit integer of range [0..7]
   Range8 ::= SEQUENCE {
      start Integer8,
      length Integer8
   }
   -- 4-bit integer of range [0..15]
   Range16 ::= SEQUENCE {
      start Integer16,
      length Integer16
   }
   -- Any size of interger
   Range ::= SEQUENCE {
      start INTEGER,
      length INTEGER
   }

   -- 2-bit flexible range [0..3]
   FlexibleRange4 ::= SEQUENCE {
      -- The count of single sequence [1..4] which is
      -- a 2-bit count
      single SEQUENCE SIZE(1..4) OF Integer4 OPTIONAL,
      -- The intenger range is [0..3]
      range SEQUENCE OF Range4 OPTIONAL
   }

   -- 3-bit flexible range [0..7]
   FlexibleRange8 ::= SEQUENCE {
      -- The count of single sequence [1..8] which is 
      -- a 3-bit count
      single SEQUENCE SIZE(1..8) OF Integer8 OPTIONAL,
      -- The intenger range is [0..7]
      range SEQUENCE OF Range8 OPTIONAL
   }

   -- 4-bit flexible range [0..15]
   FlexibleRange16 ::= SEQUENCE {
      -- The count of single sequence [1..16] which is
      -- a 4-bit count
      single SEQUENCE SIZE(1..16) OF Integer8 OPTIONAL,
      -- The intenger range is [0..15]
      range SEQUENCE OF Range16 OPTIONAL
   }
   -- Any size of flexible range
   FlexibleRange ::= SEQUENCE {
      single SEQUENCE OF INTEGER OPTIONAL,
      range SEQUENCE OF Range OPTIONAL
   }
END

Debug-Extension
DEFINITIONS
   AUTOMATIC TAGS ::=
BEGIN
   EXPORTS Debug, DebugModule;
   IMPORTS FlexibleRange FROM Helper-Types;

   TriggerAction ::= SEQUENCE {
      breakpointExceptionSupported BOOLEAN DEFAULT FALSE,
      debugModeSupported BOOLEAN DEFAULT FALSE,
      -- TODO: Add trace actions
      external0Supported BOOLEAN DEFAULT FALSE,
      external1Supported BOOLEAN DEFAULT FALSE,
      ...
   }

   TriggerModes ::= SEQUENCE {
      m BOOLEAN DEFAULT FALSE,
      s BOOLEAN DEFAULT FALSE,
      u BOOLEAN DEFAULT FALSE,
      vs BOOLEAN DEFAULT FALSE,
      vu BOOLEAN DEFAULT FALSE,
      ...
   }

   TriggerMcontrol ::= SEQUENCE {
      maskmax INTEGER (0..63),
      selectSupported ENUMERATED {address, data, both},
      timingSupported ENUMERATED {before, after, both},
      addressMatch BOOLEAN DEFAULT FALSE,
      dataMatch BOOLEAN DEFAULT FALSE,
      sizeAny BOOLEAN DEFAULT FALSE,
      size8 BOOLEAN DEFAULT FALSE,
      size16 BOOLEAN DEFAULT FALSE,
      size32 BOOLEAN DEFAULT FALSE,
      size64 BOOLEAN DEFAULT FALSE,
      size80 BOOLEAN DEFAULT FALSE,
      size96 BOOLEAN DEFAULT FALSE,
      size112 BOOLEAN DEFAULT FALSE,
      size128 BOOLEAN DEFAULT FALSE,
      chainSupported BOOLEAN DEFAULT FALSE,
      matchEqual BOOLEAN DEFAULT FALSE,
      matchNapot BOOLEAN DEFAULT FALSE,
      matchGreaterEqual BOOLEAN DEFAULT FALSE,
      matchLess BOOLEAN DEFAULT FALSE,
      matchLowMask BOOLEAN DEFAULT FALSE,
      matchHighMask BOOLEAN DEFAULT FALSE,
      matchNotEqual BOOLEAN DEFAULT FALSE,
      matchNotNapot BOOLEAN DEFAULT FALSE,
      matchNotLowMask BOOLEAN DEFAULT FALSE,
      matchNotHighMask BOOLEAN DEFAULT FALSE,
      executeSupported BOOLEAN DEFAULT FALSE,
      storeSupported BOOLEAN DEFAULT FALSE,
      loadSupported BOOLEAN DEFAULT FALSE,
      ...
   }

   TriggerMcontrol6 ::= SEQUENCE {
      maskmax INTEGER (0..63),
      selectSupported ENUMERATED {address, data, both},
      timingSupported ENUMERATED {before, after, both},
      addressMatch BOOLEAN DEFAULT FALSE,
      dataMatch BOOLEAN DEFAULT FALSE,
      sizeAny BOOLEAN DEFAULT FALSE,
      size8 BOOLEAN DEFAULT FALSE,
      size16 BOOLEAN DEFAULT FALSE,
      size32 BOOLEAN DEFAULT FALSE,
      size64 BOOLEAN DEFAULT FALSE,
      size80 BOOLEAN DEFAULT FALSE,
      size96 BOOLEAN DEFAULT FALSE,
      size112 BOOLEAN DEFAULT FALSE,
      size128 BOOLEAN DEFAULT FALSE,
      chainSupported BOOLEAN DEFAULT FALSE,
      matchEqual BOOLEAN DEFAULT FALSE,
      matchNapot BOOLEAN DEFAULT FALSE,
      matchGreaterEqual BOOLEAN DEFAULT FALSE,
      matchLess BOOLEAN DEFAULT FALSE,
      matchLowMask BOOLEAN DEFAULT FALSE,
      matchHighMask BOOLEAN DEFAULT FALSE,
      matchNotEqual BOOLEAN DEFAULT FALSE,
      matchNotNapot BOOLEAN DEFAULT FALSE,
      matchNotLowMask BOOLEAN DEFAULT FALSE,
      matchNotHighMask BOOLEAN DEFAULT FALSE,
      executeSupported BOOLEAN DEFAULT FALSE,
      storeSupported BOOLEAN DEFAULT FALSE,
      loadSupported BOOLEAN DEFAULT FALSE,
      ...
   }

   TriggerIcount ::= SEQUENCE {
      countMax INTEGER (1..16383),
      ...
   }

   TriggerItrigger ::= SEQUENCE {
      supported NULL,
      -- Intentionally not describing possible tdata2 values. TODO: Should we?
      -- Certainly it's an implementation decision which interrupts we can
      -- trigger on, but it's fairly easy to discover which values are valid.
      -- Where exactly do we draw the line on how much detail to describe?
      ...
   }

   TriggerEtrigger ::= SEQUENCE {
      nmiSupported BOOLEAN,
      ...
   }

   TriggerTmexttrigger ::= SEQUENCE {
      intctlSupported BOOLEAN,
      selectSupported BIT STRING, -- TODO: Constrain length
      ...
   }

   DebugTrigger ::= SEQUENCE {
      -- Which triggers does this description apply to?
      index FlexibleRange,

      -- Technically these could differ depending on the precise arguments given
      -- to the trigger, but that would be a very strange implementation.
      hitSupported BOOLEAN DEFAULT FALSE,
      actionSupported TriggerAction,
      -- If TriggerModes is not supplied, it is assumed that the triggers
      -- support every mode that the hart supports.
      modeSupported TriggerModes OPTIONAL,

      mcontrol SEQUENCE OF TriggerMcontrol OPTIONAL,
      mcontrol6 SEQUENCE OF TriggerMcontrol6 OPTIONAL,
      icount SEQUENCE OF TriggerIcount OPTIONAL,
      itrigger SEQUENCE OF TriggerItrigger OPTIONAL,
      etrigger SEQUENCE OF TriggerEtrigger OPTIONAL,
      ...
   }

   ContextInfo ::= SEQUENCE {
      -- Keep this in its own section which is optional, since tiny cores won't
      -- have any of these modes, and can then encode in a single bit they have
      -- none of this.
      hcxeSupported BOOLEAN DEFAULT FALSE,
      scxeSupported BOOLEAN DEFAULT FALSE,
      mpteSupported BOOLEAN DEFAULT FALSE,
      mteSupported BOOLEAN DEFAULT FALSE,
      hcontextSupported BOOLEAN DEFAULT FALSE,
      scontextSupported BOOLEAN DEFAULT FALSE,
      mcontextSupported BOOLEAN DEFAULT FALSE,
      ...
   }

   AccessRegisterCommand ::= SEQUENCE {
      -- I'd like to use a BIT STRING for the size, but JER format doesn't let
      -- you use symbolic names for them.
      aarsize32Supported BOOLEAN DEFAULT FALSE,
      aarsize64Supported BOOLEAN DEFAULT FALSE,
      aarsize128Supported BOOLEAN DEFAULT FALSE,
      aarpostincrementSupported BOOLEAN DEFAULT FALSE,
      postexecSupported BOOLEAN DEFAULT FALSE,
      regno FlexibleRange,
      ...
   }
   
   QuickAccessCommand ::= SEQUENCE {
      -- A SEQUENCE cannot be empty, so we have to put something in here. NULL
      -- takes no space to encode.
      supported NULL,
      ...
   }

   AccessMemoryCommand ::= SEQUENCE {
      aamvirtual0 BOOLEAN DEFAULT FALSE,
      aamvirtual1 BOOLEAN DEFAULT FALSE,
      aamsize8 BOOLEAN DEFAULT FALSE,
      aamsize16 BOOLEAN DEFAULT FALSE,
      aamsize32 BOOLEAN DEFAULT FALSE,
      aamsize64 BOOLEAN DEFAULT FALSE,
      aamsize128 BOOLEAN DEFAULT FALSE,
      aampostincrementSupported BOOLEAN DEFAULT FALSE,
      writeSupported BOOLEAN DEFAULT FALSE,
      readSupported BOOLEAN DEFAULT FALSE,
      ...
   }

   -- Configuration information regarding basic run control, selecting harts,
   -- reset, etc.
   RunControl ::= SEQUENCE {
      hartresetSupported BOOLEAN DEFAULT FALSE,
      -- If hartselLen is 0, hasel is tied to 0.
      hartselLen INTEGER (0..20) DEFAULT 0,
      keepaliveSupported BOOLEAN DEFAULT FALSE,
      resethaltreqSuported BOOLEAN DEFAULT FALSE,
      haltGroupCount INTEGER (1..31) OPTIONAL,
      resumeGroupCount INTEGER (1..31) OPTIONAL,
      ...
   }

   -- Configuration information regarding abstract commands.
   Abstract ::= SEQUENCE {
      relaxedprivSupported BOOLEAN DEFAULT FALSE,
      -- We want this to be variable length, because usually only a few low bits
      -- will be set. I'd like to constrain the length so people cannot specify
      -- something non-sensical.
      autoexecprogbuf BIT STRING DEFAULT ''B, -- TODO: Constrain length to 16 bits
      autoexecdata BIT STRING DEFAULT ''B, -- TODO: Constrain length to 12 bits

      -- Enumerate every supported abstract command. It is not required to list
      -- AccessRegisterCommand for the GPRs since that functionality is required
      -- by the spec.
      accessRegister SEQUENCE OF AccessRegisterCommand OPTIONAL,
      quickAccess SEQUENCE OF QuickAccessCommand OPTIONAL,
      accessMemory SEQUENCE OF AccessMemoryCommand OPTIONAL,

      ...
   }

   HartInfo ::= SEQUENCE {
      hartid FlexibleRange,
      nscratch INTEGER (0..15) DEFAULT 0,
      dataaccess CHOICE {
         none NULL,
         csr SEQUENCE {
            count INTEGER (1..15),
            address INTEGER(0..4095)
         },
         memory SEQUENCE {
            wordCount INTEGER (1..15),
            address INTEGER (-2048..2047)
         }
      },
      ...
   }

   -- Information about a debug module that is trivial to read. This section is
   -- helpful for descriptions of the hardware when the hardware itself is not
   -- accessible.
   DebugModuleComplete ::= SEQUENCE {
      stickyunavail BOOLEAN DEFAULT FALSE,
      impebreak BOOLEAN DEFAULT FALSE,
      hasresethaltreq BOOLEAN DEFAULT FALSE,
      confstrptrvalid BOOLEAN DEFAULT FALSE,
      version ENUMERATED {v0-11, v0-13, v1-0, ...},

      hartInfo SEQUENCE OF HartInfo OPTIONAL,

      progbufsize INTEGER (0..16) DEFAULT 0,
      datacount INTEGER (1..12) DEFAULT 1,

      -- TODO: Figure out what to do about confstrptr. Should it be included?
      sbversion INTEGER (0..7),
      sbasize INTEGER (0..127),
      sbaccess128Supported BOOLEAN DEFAULT FALSE,
      sbaccess64Supported BOOLEAN DEFAULT FALSE,
      sbaccess32Supported BOOLEAN DEFAULT FALSE,
      sbaccess16Supported BOOLEAN DEFAULT FALSE,
      sbaccess8Supported BOOLEAN DEFAULT FALSE,
      ...
   }

   -- Describes a debug module that sits outside a hart.
   DebugModule ::= SEQUENCE {
      -- Where this DM is in the chain of DMs. Will almost always be 0.
      index INTEGER DEFAULT 0,
      -- Which harts are connected to this DM, identified by hart ID.
      connectedHarts FlexibleRange OPTIONAL,

      -- DMI address of this debug module. Will almost always be 0, in which
      -- case it can be omitted.
      dmiAddress INTEGER DEFAULT 0,

      abstract Abstract,
      runControl RunControl,
      complete DebugModuleComplete OPTIONAL,

      -- TODO: Should we put vendorExtension SEQUENCE OF OCTET STRING OPTIONAL here?
      ...
   }

   DebugComplete ::= SEQUENCE {
      debugver INTEGER (1..15),
      ...
   }

   -- Describes the debug features built into a specific hart.
   Debug ::= SEQUENCE {
      stepieSupported BOOLEAN DEFAULT FALSE,
      stopcountSupported BOOLEAN DEFAULT FALSE,
      stoptimeSupported BOOLEAN DEFAULT FALSE,
      mprvenSupported ENUMERATED {on, off, both} DEFAULT off,

      contextInfo ContextInfo OPTIONAL,
      trigger SEQUENCE OF DebugTrigger OPTIONAL,
      complete DebugComplete OPTIONAL,
      ...
   }
END

Zjpm-Extension
DEFINITIONS
   AUTOMATIC TAGS ::=
BEGIN
   EXPORTS Zjpm;

   Zjpm ::= SEQUENCE {
      -- 1 bit to indicate whether the pointer masking extension is present.
      -- If this extension is included, it's assumed pointer masking is present.

      -- 1 bit to indicate whether pointer masking for instructions is supported.
      pmInstruction BOOLEAN DEFAULT FALSE,

      -- 4 bits (1 bit per privilege level) to indicate whether pointer masking
      -- is supported at that privilege level.
      mSupported BOOLEAN DEFAULT FALSE,
      sSupported BOOLEAN DEFAULT FALSE,
      vSupported BOOLEAN DEFAULT FALSE,
      uSupported BOOLEAN DEFAULT FALSE,

      -- 5/6/7 bits (for RV32/64/128) to indicate how many bits from the top are
      -- maskable.
      maskBitcount INTEGER (1..128),

      -- 1 bit to indicate whether any additional (non-contiguous) bits are
      -- maskable.
      nonContiguousMaskable BOOLEAN DEFAULT FALSE
   }
END
