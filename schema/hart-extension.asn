Hart-Extension
DEFINITIONS
   AUTOMATIC TAGS ::=
BEGIN
   EXPORTS Isa;
   
   Isa ::= SEQUENCE {
      riscv32 BOOLEAN OPTIONAL,
      riscv64 BOOLEAN OPTIONAL,
      riscv128 BOOLEAN OPTIONAL,
      ...
   }
END
