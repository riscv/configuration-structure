Helper-Types
DEFINITIONS
   AUTOMATIC TAGS ::=
BEGIN
   EXPORTS FlexibleRange, FlexibleRange2, FlexibleRange3, FlexibleRange4,
           Range, Tuple, Triple, PossibleValues, PhysicalAddress, Translation,
           Version, Rv32I, Rv64I;

   -- 2-bit integer
   Integer2 ::= INTEGER (0..3)

   -- 3-bit integer
   Integer3 ::= INTEGER (0..7)

   -- 4-bit integer
   Integer4 ::= INTEGER (0..15)

   -- 2-bit integer of range [0..3]
   Range2 ::= SEQUENCE {
      start Integer2,
      length Integer2
   }
   -- 3-bit integer of range [0..7]
   Range3 ::= SEQUENCE {
      start Integer3,
      length Integer3
   }
   -- 4-bit integer of range [0..15]
   Range4 ::= SEQUENCE {
      start Integer4,
      length Integer4
   }
   -- Any size of interger
   Range ::= SEQUENCE {
      start INTEGER (0..MAX),
      length INTEGER (0..MAX)
   }

   -- Any size of flexible range
   FlexibleRange2 ::= CHOICE {
      -- If this list is empty, the user must assume it contains a single entry
      -- that is 0.
      single SEQUENCE SIZE(0..3) OF Integer2,
      range SEQUENCE SIZE(1..2) OF Integer2
   }
   -- Any size of flexible range
   FlexibleRange3 ::= CHOICE {
      -- If this list is empty, the user must assume it contains a single entry
      -- that is 0.
      single SEQUENCE SIZE(0..7) OF Integer3,
      range SEQUENCE SIZE(1..4) OF Integer3
   }
   -- Any size of flexible range
   FlexibleRange4 ::= CHOICE {
      -- If this list is empty, the user must assume it contains a single entry
      -- that is 0.
      single SEQUENCE SIZE(0..15) OF Integer4,
      range SEQUENCE SIZE(1..8) OF Integer4
   }
   -- Any size of flexible range
   FlexibleRange ::= CHOICE {
      -- If this list is empty, the user must assume it contains a single entry
      -- that is 0.

      -- This INTEGER should be constrained to (0..MAX), but if we do that then
      -- asn1c hits a bug when generating code for it.
      single SEQUENCE OF INTEGER,
      range SEQUENCE SIZE(1..MAX) OF Range
   }

   -- Value/Mask tuple
   Tuple ::= SEQUENCE {
      value INTEGER,
      mask INTEGER
   }
   -- Low/High with mask applied
   Triple ::= SEQUENCE {
      low INTEGER,
      high INTEGER,
      mask INTEGER
   }
   -- Possible value formats
   PossibleValues ::= SEQUENCE {
      tuple SEQUENCE OF Tuple OPTIONAL,
      triple SEQUENCE OF Triple OPTIONAL,
      ...
   }

   Translation ::= SEQUENCE OF SEQUENCE {
      -- Translate an input value x to an output value y.
      -- If x is in range, y = multiply * x + offset
      -- Otherwise y = x
      range Range,
      offset INTEGER DEFAULT 0,
      multiply INTEGER DEFAULT 1
   }

   -- A physical address, stored with the least-significant byte first.
   -- Any bytes that are not stored are assumed to be 0.
   PhysicalAddress ::= OCTET STRING (SIZE(1..16))

   Version ::= SEQUENCE {
      major	INTEGER (0..255),
      minor	INTEGER (0..255)
   }

   Rv32I ::= SEQUENCE {
      version Version OPTIONAL,
      ...
   }

   Rv64I ::= SEQUENCE {
      version Version OPTIONAL,
      ...
   }

END
