Configuration-Structure-Schema DEFINITIONS AUTOMATIC TAGS ::= BEGIN
   Range ::= SEQUENCE {
      start INTEGER,
      length INTEGER 
   }
   FlexibleRange ::= SEQUENCE {
      single INTEGER OPTIONAL,
      start INTEGER OPTIONAL,
      end INTEGER OPTIONAL,
      ...
   }
   Hart ::= SEQUENCE {
      hartid SEQUENCE OF FlexibleRange,
      debug Debug OPTIONAL,
      isa Isa OPTIONAL,
      privileged Privileged OPTIONAL,
      clic Clic OPTIONAL,
      fastint Fastint OPTIONAL,
      ...
   }
   Tuple ::= SEQUENCE {
      value INTEGER,
      mask INTEGER
   }
   Triple ::= SEQUENCE {
      low INTEGER,
      high INTEGER,
      mask INTEGER
   }
   PossibleValues ::= SEQUENCE {
      tuple SEQUENCE OF Tuple OPTIONAL,
      triple SEQUENCE OF Triple OPTIONAL,
      ...
   }
   Configuration ::= SEQUENCE {
      harts SEQUENCE (SIZE(1..64)) OF Hart OPTIONAL,
      debugModule SEQUENCE OF DebugModule OPTIONAL,
      traceModule TraceModule OPTIONAL,
      physicalMemory SEQUENCE OF PhysicalMemory OPTIONAL,
      ...
   }
   DebugTriggerMcontrol ::= SEQUENCE {
      maskmax INTEGER,
      hit BOOLEAN,
      addressMatch BOOLEAN,
      dataMatch BOOLEAN,
      timingBefore BOOLEAN,
      timingAfter BOOLEAN,
      sizeAny BOOLEAN,
      sizeS8 BOOLEAN,
      sizeS16 BOOLEAN,
      sizeS32 BOOLEAN,
      sizeS64 BOOLEAN,
      sizeS80 BOOLEAN,
      sizeS96 BOOLEAN,
      sizeS112 BOOLEAN,
      sizeS128 BOOLEAN,
      actionMmode BOOLEAN,
      actionDmode BOOLEAN,
      chain BOOLEAN,
      matchEqual BOOLEAN,
      matchNapot BOOLEAN,
      matchGreaterEqual BOOLEAN,
      matchLess BOOLEAN,
      matchLowMask BOOLEAN,
      matchHighMask BOOLEAN,
      matchNotEqual BOOLEAN,
      matchNotNapot BOOLEAN,
      matchNotLowMask BOOLEAN,
      matchNotHighMask BOOLEAN,
      m BOOLEAN,
      s BOOLEAN,
      u BOOLEAN,
      execute BOOLEAN,
      store BOOLEAN,
      load BOOLEAN
   }
   DebugTriggerMcontrolCompact ::= SEQUENCE {
      bitfield INTEGER
   }
   DebugTrigger ::= SEQUENCE {
      index FlexibleRange,
      mcontrol SEQUENCE OF DebugTriggerMcontrol OPTIONAL,
      mcontrolcompact SEQUENCE OF DebugTriggerMcontrolCompact OPTIONAL,
      ...
   }
   AccessRegisterCommand ::= SEQUENCE {
      aarsize32 BOOLEAN,
      aarsize64 BOOLEAN,
      aarsize128 BOOLEAN,
      aarpostincrementSupported BOOLEAN,
      postexecSupported BOOLEAN,
      regno FlexibleRange
   }
   AccessMemoryCommand ::= SEQUENCE {
      aamvirtual0 BOOLEAN,
      aamvirtual1 BOOLEAN,
      aamsize8 BOOLEAN,
      aamsize16 BOOLEAN,
      aamsize32 BOOLEAN,
      aamsize64 BOOLEAN,
      aamsize128 BOOLEAN,
      aampostincrementSupported BOOLEAN,
      writeSupported BOOLEAN,
      readSupported BOOLEAN
   }
   AbstractCommand ::= SEQUENCE {
      accessRegister SEQUENCE OF AccessRegisterCommand OPTIONAL,
      quickAccess SEQUENCE OF BOOLEAN OPTIONAL,
      accessMemory SEQUENCE OF AccessMemoryCommand OPTIONAL,
      ...
   }
   DebugModule ::= SEQUENCE {
      index INTEGER OPTIONAL,
      abstract AbstractCommand OPTIONAL,
      connectedHarts FlexibleRange OPTIONAL,
      ...
   }
   Debug ::= SEQUENCE {
      trigger SEQUENCE OF DebugTrigger OPTIONAL,
      ...
   }
   Isa ::= SEQUENCE {
      riscv32 BOOLEAN OPTIONAL,
      riscv64 BOOLEAN OPTIONAL,
      riscv128 BOOLEAN OPTIONAL,
      ...
   }
   PrivModes ::= SEQUENCE {
      u BOOLEAN OPTIONAL,
      m BOOLEAN,
      s BOOLEAN OPTIONAL
   }
   PrivSatps ::= SEQUENCE {
      sv32 BOOLEAN,
      sv39 BOOLEAN,
      sv48 BOOLEAN,
      sv57 BOOLEAN,
      sv64 BOOLEAN
   }
   Privileged ::= SEQUENCE {
      modes PrivModes OPTIONAL,
      satps PrivSatps OPTIONAL,
      epmp BOOLEAN OPTIONAL,
      ...
   }
   Clic ::= SEQUENCE {
      mTimeRegisterAddress INTEGER OPTIONAL,
      mTimeCompareRegisterAddress INTEGER OPTIONAL,
      ...
   }
   FastInterruptModule ::= SEQUENCE {
      index SEQUENCE OF Range OPTIONAL,
      connectedHarts SEQUENCE OF Range OPTIONAL,
      ...
   }
   TraceModule ::= SEQUENCE {
      branchpredictorentries INTEGER OPTIONAL,
      jumptargetcacheentries INTEGER OPTIONAL,
      contextbuswidth INTEGER OPTIONAL,
      ...
   }
   PhysicalMemory ::= SEQUENCE {
      address SEQUENCE OF Range,
      cacheable BOOLEAN OPTIONAL,
      lrScSupported BOOLEAN OPTIONAL,
      ...
   }
   Fastint ::= SEQUENCE {
      mmodetimeregaddr INTEGER OPTIONAL,
      mmodetimecompregaddr INTEGER OPTIONAL,
      ...
   }
END
