World-Schema DEFINITIONS AUTOMATIC TAGS ::= BEGIN
   Range ::= SEQUENCE {
      start INTEGER,
      length INTEGER
   }
   FlexibleRange ::= SEQUENCE {
      single SEQUENCE OF INTEGER,
      start SEQUENCE OF INTEGER,
      end SEQUENCE OF INTEGER,
      ...
   }
   Hart ::= SEQUENCE {
      hartid FlexibleRange,
      debug Debug,
      isa Isa,
      privileged Privileged,
      clic Clic,
      fastint Fastint,
      ...
   }
   Tuple ::= SEQUENCE {
      value INTEGER,
      mask INTEGER
   }
   Triple ::= SEQUENCE {
      low INTEGER,
      high INTEGER,
      mask INTEGER
   }
   PossibleValues ::= SEQUENCE {
      tuple SEQUENCE OF Tuple,
      triple SEQUENCE OF Triple,
      ...
   }
   Configuration ::= SEQUENCE {
      harts SEQUENCE OF Hart,
      debugModule SEQUENCE OF DebugModule,
      traceModule TraceModule,
      physicalMemory SEQUENCE OF PhysicalMemory,
      ...
   }
   DebugTriggerMcontrol ::= SEQUENCE {
      maskmax INTEGER (0..31),
      hit BOOLEAN,
      addressMatch BOOLEAN,
      dataMatch BOOLEAN,
      timingBefore BOOLEAN,
      timingAfter BOOLEAN,
      sizeAny BOOLEAN,
      sizeS8 BOOLEAN,
      sizeS16 BOOLEAN,
      sizeS32 BOOLEAN,
      sizeS64 BOOLEAN,
      sizeS80 BOOLEAN,
      sizeS96 BOOLEAN,
      sizeS112 BOOLEAN,
      sizeS128 BOOLEAN,
      actionMmode BOOLEAN,
      actionDmode BOOLEAN,
      chain BOOLEAN,
      matchEqual BOOLEAN,
      matchNapot BOOLEAN,
      matchGreaterEqual BOOLEAN,
      matchLess BOOLEAN,
      matchLowMask BOOLEAN,
      matchHighMask BOOLEAN,
      matchNotEqual BOOLEAN,
      matchNotNapot BOOLEAN,
      matchNotLowMask BOOLEAN,
      matchNotHighMask BOOLEAN,
      m BOOLEAN,
      s BOOLEAN,
      u BOOLEAN,
      execute BOOLEAN,
      store BOOLEAN,
      load BOOLEAN
   }
   DebugTriggerMcontrolCompact ::= SEQUENCE {
      bitfield INTEGER
   }
   DebugTrigger ::= SEQUENCE {
      index FlexibleRange,
      mcontrol SEQUENCE OF DebugTriggerMcontrol,
      mcontrolcompact SEQUENCE OF DebugTriggerMcontrolCompact,
      ...
   }
   AccessRegisterCommand ::= SEQUENCE {
      aarsize32 BOOLEAN,
      aarsize64 BOOLEAN,
      aarsize128 BOOLEAN,
      aarpostincrementSupported BOOLEAN,
      postexecSupported BOOLEAN,
      regno FlexibleRange
   }
   AccessMemoryCommand ::= SEQUENCE {
      aamvirtual0 BOOLEAN,
      aamvirtual1 BOOLEAN,
      aamsize8 BOOLEAN,
      aamsize16 BOOLEAN,
      aamsize32 BOOLEAN,
      aamsize64 BOOLEAN,
      aamsize128 BOOLEAN,
      aampostincrementSupported BOOLEAN,
      writeSupported BOOLEAN,
      readSupported BOOLEAN
   }
   AbstractCommand ::= SEQUENCE {
      accessRegister SEQUENCE OF AccessRegisterCommand,
      quickAccess SEQUENCE OF BOOLEAN,
      accessMemory SEQUENCE OF AccessMemoryCommand,
      ...
   }
   DebugModule ::= SEQUENCE {
      index INTEGER,
      abstract AbstractCommand,
      connectedHarts FlexibleRange,
      ...
   }
   Debug ::= SEQUENCE {
      trigger SEQUENCE OF DebugTrigger,
      ...
   }
   Isa ::= SEQUENCE {
      riscv32 BOOLEAN,
      riscv64 BOOLEAN,
      riscv128 BOOLEAN,
      ...
   }
   PrivModes ::= SEQUENCE {
      u BOOLEAN,
      m BOOLEAN,
      s BOOLEAN
   }
   PrivSatps ::= SEQUENCE {
      sv32 BOOLEAN,
      sv39 BOOLEAN,
      sv48 BOOLEAN,
      sv57 BOOLEAN,
      sv64 BOOLEAN
   }
   Privileged ::= SEQUENCE {
      modes PrivModes,
      satps PrivSatps,
      epmp BOOLEAN,
      ...
   }
   Clic ::= SEQUENCE {
      mTimeRegisterAddress INTEGER,
      mTimeCompareRegisterAddress INTEGER,
      ...
   }
   FastInterruptModule ::= SEQUENCE {
      index SEQUENCE OF Range,
      connectedHarts SEQUENCE OF Range,
      ...
   }
   TraceModule ::= SEQUENCE {
      branchpredictorentries INTEGER,
      jumptargetcacheentries INTEGER,
      contextbuswidth INTEGER,
      ...
   }
   PhysicalMemory ::= SEQUENCE {
      address SEQUENCE OF Range,
      cacheable BOOLEAN,
      lrScSupported BOOLEAN,
      ...
   }
   Fastint ::= SEQUENCE {
      mmodetimeregaddr INTEGER,
      mmodetimecompregaddr INTEGER,
      ...
   }
END
